;Función para leer información de la plantilla.
(defun C:LEERPLANT ()
  (setq plantilla (open (strcat (findfile "Archivos_salaCAD_David_Aguirre") "\\Plantilla.txt") "r"))
  (setq atributostotal 1)
  
  (setq renfut (read-line plantilla))
  
  
  (while (/= (/= renfut nil) nil)
    (setq renfut (read-line plantilla))
    (setq atributostotal (+ atributostotal 1))
  )
  (setq plantilla (open (strcat (findfile "Archivos_salaCAD_David_Aguirre") "\\Plantilla.txt") "r"))
  (setq renglon 1)
  (setq renact "")
  (setq ch 1)
  
  (setq renfut (read-line plantilla))
  (setq infoplantilla (vlax-make-safearray vlax-vbString (cons 1 (- atributostotal 1)) (cons 1 4)))
  
  (while (/= (/= renfut nil) nil)
    (setq renact renfut)
    (repeat (strlen renact)
      (if (= (substr renact ch 1) " ")
        (progn
          (setq infoplant (substr renact (+ ch 1)))
          (vlax-safearray-put-element infoplantilla renglon 1 (substr renact 1 (- ch 1)))
          (vlax-safearray-put-element infoplantilla renglon 2 (substr infoplant 1 1))
          (vlax-safearray-put-element infoplantilla renglon 3 (substr infoplant 2 3))
          (vlax-safearray-put-element infoplantilla renglon 4 (substr infoplant 5 3))
        )
      )
      (setq ch (+ ch 1))
    )
    (setq renglon (+ renglon 1))
    (setq ch 1)
    (setq renfut (read-line plantilla))
  )
)

;Función obtenida de internet para leer fácilmente archivos de excel.
(defun C:GetCells ()
 (defun getCellsFunction(fileName sheetName cellName / myXL myBook mySheet myRange cellValue)
 (setq myXL(vlax-get-or-create-object "Excel.Application"))
 (vla-put-visible myXL :vlax-false)
 (vlax-put-property myXL 'DisplayAlerts :vlax-false)
 (setq myBook (vl-catch-all-apply 'vla-open (list (vlax-get-property myXL "WorkBooks") fileName)))
 (setq mySheet (vl-catch-all-apply 'vlax-get-property (list (vlax-get-property myBook "Sheets") "Item" sheetName)))
 (vlax-invoke-method mySheet "Activate")
 (setq myRange (vlax-get-property (vlax-get-property mySheet 'Cells) "Range" cellName))
 (setq cellValue(vlax-variant-value (vlax-get-property myRange 'Value2)))
 (vl-catch-all-apply 'vlax-invoke-method (list myBook "Close"))
 (vl-catch-all-apply 'vlax-invoke-method (list myXL "Quit"))
 (if (not (vlax-object-released-p myRange))(progn(vlax-release-object myRange)(setq myRange nil)))
 (if (not (vlax-object-released-p mySheet))(progn(vlax-release-object mySheet)(setq mySheet nil)))
 (if (not (vlax-object-released-p myBook))(progn(vlax-release-object myBook)(setq myBook nil)))
 (if (not (vlax-object-released-p myXL))(progn(vlax-release-object myXL)(setq myXL nil)))
 (if(= 'safearray (type cellValue))
 (progn
 (setq tempCellValue(vlax-safearray->list cellValue))
 (setq cellValue(list))
 (if(= (length tempCellValue) 1)
 (progn
 (foreach a tempCellValue
 (if(= (type a) 'LIST)
 (progn
 (foreach b a
 (if(= (type b) 'LIST)
 (setq cellValue(append cellValue (list (vlax-variant-value (car b)))))
 (setq cellValue(append cellValue (list (vlax-variant-value b))))
 )
 )
 )
 (setq cellValue(append cellValue (list (vlax-variant-value a))))
 )
 )
 )
 (progn
 (foreach a tempCellValue
 (setq tmpList(list))
 (foreach b a
 (setq tmp(vlax-variant-value b))
 (setq tmpList(append tmpList (list tmp)))
 )
 (setq cellValue(append cellValue tmpList))
 )
 )
 )
 )
 )
 cellValue
 )
)

;Función para leer archivo separado por comas y dibujar sala CAD.
(defun C:ASC ()
  (setq plantilla (open (strcat (findfile "Archivos_salaCAD_David_Aguirre") "\\ASC.txt") "r"))
  (setq elementos 1)
  (setq renfut (read-line plantilla))
  
  (while (/= (/= renfut nil) nil)
    (setq renfut (read-line plantilla))
    (setq elementos (+ elementos 1))
  )
  
  (setq mesacoma (open (strcat (findfile "Archivos_salaCAD_David_Aguirre") "\\ASC.txt") "r"))
  (setq nf -1)
  (setq renact "")
  (setq ch 1)
  (setq ci 1)
  (setq renglon 1)
  (setq atributos 1)
  (setq infocomas (vlax-make-safearray vlax-vbString (cons 1 (- elementos 1)) (cons 1 (- atributostotal 1))))
  
  (setq renfut (read-line mesacoma))
  (while (/= (/= renfut nil) nil)
    (setq renact renfut)
    (repeat (strlen renact)
      (if (= (substr renact ch 1) ",")
        (progn
          (vlax-safearray-put-element infocomas renglon atributos (substr renact ci (- ch ci)))
          (setq ci (+ ch 1))
          (setq atributos (+ atributos 1))
          (setq ch (+ ch 1))
        )
        (setq ch (+ ch 1))
      )
      (if (= ch (strlen renact))
        (vlax-safearray-put-element infocomas renglon atributos (substr renact ci (+ (- ch ci) 1)))
      )
    )
    (setq atributos 1)
    (setq ci 1)
    (setq renglon (+ renglon 1))
    (setq ch 1)
    (setq nf (+ nf 1))
    (setq renfut (read-line mesacoma))
  )
  ;Dibujo de la sala CAD.
  (setq nombres (vlax-make-safearray vlax-vbString '(1 . 6)))
  
  (vlax-safearray-put-element nombres 1 "CuadernoE.dwg")
  (vlax-safearray-put-element nombres 2 "MonitorE.dwg")
  (vlax-safearray-put-element nombres 3 "PhoneE.dwg")
  (vlax-safearray-put-element nombres 4 "MouseE.dwg")
  (vlax-safearray-put-element nombres 5 "TecladoE.dwg")
  (vlax-safearray-put-element nombres 6 "SillaE.dwg")
  
  (setq j 0)
  (setq k 500)
  (repeat 4
    (setq i 1)
    
    (repeat (- elementos 1)
      (setq cordx (vlax-safearray-get-element infocomas i 2))
      (setq cordy (vlax-safearray-get-element infocomas i 3))
      (setq cordz (vlax-safearray-get-element infocomas i 4))
      (setq cordxn (+ (read cordx) j))
      (setq cordx (rtos cordxn 2 6))
      (command "_insert" (strcat (findfile "Archivos_salaCAD_David_Aguirre") "\\" (vlax-safearray-get-element nombres i)) (strcat cordx "," cordy) "1" "1" "")
      (setq i (+ i 1))
    )
    (setq mesai (strcat (rtos j 2 6) "," (rtos 0 2 6)))
    (setq mesaf (strcat (rtos (+ j 1200) 2 6) "," (rtos k 2 6)))
    (command "_rectang" mesai mesaf "")
    (setq j (+ j 1200))
  )
  (setq esp1 (strcat (rtos (+ j 400) 2 6) "," "0"))
  (setq esp2 (strcat (rtos (+ j 400) 2 6) "," "10"))
  (command "_mirror" (ssget "_A") "" "0,500" "10,500" "No")
  (command "_mirror" (ssget "_A") "" esp1 esp2 "No")
  (command "_mirror" (ssget "_A") "" "0,1500" "10,1500" "No")

)
;Función para leer archivo separado por espacios y dibujar sala CAD.
(defun C:ASE ()
  (setq archivoesp (open (strcat (findfile "Archivos_salaCAD_David_Aguirre") "\\ASE.txt") "r"))
  (setq elementos 1)
  
  (setq renfut (read-line archivoesp))
  
  
  (while (/= (/= renfut nil) nil)
    (setq renfut (read-line archivoesp))
    (setq elementos (+ elementos 1))
  )
  
  (setq mesaespacio (open (strcat (findfile "Archivos_salaCAD_David_Aguirre") "\\ASE.txt") "r"))
  (setq nf -1)
  (setq renact "")
  (setq ch 1)
  (setq ci 1)
  (setq renglon 1)
  (setq atributos 1)
  (setq infoespacio (vlax-make-safearray vlax-vbString (cons 1 (- elementos 1)) (cons 1 (- atributostotal 1))))
  
  (setq renfut (read-line mesaespacio))
  (while (/= (/= renfut nil) nil)
    (setq renact renfut)
    (repeat (- atributostotal 1)
      (setq longat (read (vlax-safearray-get-element infoplantilla atributos 3)))
      (if (= "C" (vlax-safearray-get-element infoplantilla atributos 2))
        (vlax-safearray-put-element infoespacio renglon atributos (vl-string-right-trim " " (substr renact ci longat)))
        (vlax-safearray-put-element infoespacio renglon atributos (vl-string-left-trim " " (substr renact ci longat)))
      )
      (setq ci (+ ci longat))
      (setq atributos (+ atributos 1))
    )
    (setq atributos 1)
    (setq ci 1)
    (setq renglon (+ renglon 1))
    (setq ch 1)
    (setq renfut (read-line mesaespacio))
  )
  
  (setq nombres (vlax-make-safearray vlax-vbString '(1 . 6)))
  
  (vlax-safearray-put-element nombres 1 "CuadernoE.dwg")
  (vlax-safearray-put-element nombres 2 "MonitorE.dwg")
  (vlax-safearray-put-element nombres 3 "PhoneE.dwg")
  (vlax-safearray-put-element nombres 4 "MouseE.dwg")
  (vlax-safearray-put-element nombres 5 "TecladoE.dwg")
  (vlax-safearray-put-element nombres 6 "SillaE.dwg")
  
  (setq j 0)
  (setq k 500)
  (repeat 4
    (setq i 1)
    (repeat (- elementos 1)
      (setq cordx (vlax-safearray-get-element infoespacio i 2))
      (setq cordy (vlax-safearray-get-element infoespacio i 3))
      (setq cordz (vlax-safearray-get-element infoespacio i 4))
      (setq cordxn (+ (read cordx) j))
      (setq cordx (rtos cordxn 2 6))
      (command "_insert" (strcat (findfile "Archivos_salaCAD_David_Aguirre") "\\" (vlax-safearray-get-element nombres i)) (strcat cordx "," cordy) "1" "1" "")
      (setq i (+ i 1))
    )
    (setq mesai (strcat (rtos j 2 6) "," (rtos 0 2 6)))
    (setq mesaf (strcat (rtos (+ j 1200) 2 6) "," (rtos k 2 6)))
    (command "_rectang" mesai mesaf "")
    (setq j (+ j 1200))
  )
  (setq esp1 (strcat (rtos (+ j 400) 2 6) "," "0"))
  (setq esp2 (strcat (rtos (+ j 400) 2 6) "," "10"))
  (command "_mirror" (ssget "_A") "" "0,500" "10,500" "No")
  (command "_mirror" (ssget "_A") "" esp1 esp2 "No")
  (command "_mirror" (ssget "_A") "" "0,1500" "10,1500" "No")
)
;Función para leer archivo de excel y dibujar sala CAD.
(defun C:ASXL ()
  (C:GetCells)
  (setq atributostotal elementos)
  (setq elementos 7)
  (setq infoexcel (vlax-make-safearray vlax-vbString (cons 1 (- elementos 1)) (cons 1 (- atributostotal 1))))
  
  (setq cellrange (strcat "A1:" (chr (+ 63 atributostotal)) (rtos (- elementos 1) 2 6)))
  
  (setq infoexp (getCellsFunction (strcat (findfile "Archivos_salaCAD_David_Aguirre") "\\AXL.xlsx") "Hoja1" cellrange))
  
  (setq renglon 1)
  (setq atributos 1)
  (setq cont 0)
  (repeat (- elementos 1)
    (repeat (- atributostotal 1)
      (vlax-safearray-put-element infoexcel renglon atributos (nth cont infoexp))
      (setq atributos (+ atributos 1))
      (setq cont (+ cont 1))
    )
    (setq atributos 1)
    (setq renglon (+ renglon 1))
  )
  
  (setq nombres (vlax-make-safearray vlax-vbString '(1 . 6)))
  
  (vlax-safearray-put-element nombres 1 "CuadernoE.dwg")
  (vlax-safearray-put-element nombres 2 "MonitorE.dwg")
  (vlax-safearray-put-element nombres 3 "PhoneE.dwg")
  (vlax-safearray-put-element nombres 4 "MouseE.dwg")
  (vlax-safearray-put-element nombres 5 "TecladoE.dwg")
  (vlax-safearray-put-element nombres 6 "SillaE.dwg")
  
  (setq j 0)
  (setq k 500)
  (repeat 4
    (setq i 1)
    (repeat (- elementos 1)
      (setq cordx (vlax-safearray-get-element infoexcel i 2))
      (setq cordy (vlax-safearray-get-element infoexcel i 3))
      (setq cordz (vlax-safearray-get-element infoexcel i 4))
      (setq cordxn (+ (read cordx) j))
      (setq cordx (rtos cordxn 2 6))
      (command "_insert" (strcat (findfile "Archivos_salaCAD_David_Aguirre") "\\" (vlax-safearray-get-element nombres i)) (strcat cordx "," cordy) "1" "1" "")
      (setq i (+ i 1))
    )
    (setq mesai (strcat (rtos j 2 6) "," (rtos 0 2 6)))
    (setq mesaf (strcat (rtos (+ j 1200) 2 6) "," (rtos k 2 6)))
    (command "_rectang" mesai mesaf "")
    (setq j (+ j 1200))
  )
  (setq esp1 (strcat (rtos (+ j 400) 2 6) "," "0"))
  (setq esp2 (strcat (rtos (+ j 400) 2 6) "," "10"))
  (command "_mirror" (ssget "_A") "" "0,500" "10,500" "No")
  (command "_mirror" (ssget "_A") "" esp1 esp2 "No")
  (command "_mirror" (ssget "_A") "" "0,1500" "10,1500" "No")
)
;Función de ejecución del programa principal.
(defun C:SALACAD ()
  ;Eliminar lo escrito anteriormente.
  (command "mspace")
   
  (command "erase" (ssget "x")  "")
   
  (command "regen")

  (c:LEERPLANT)
  (setq pref (getstring "Elegir preferencia de archivo: coma, espacio o excel."))
  (if (= (strcase pref T) "coma")
    (progn
      (c:ASC)
    )
    (progn
      (if (= (strcase pref T) "espacio")
        (progn
          (c:ASE)
        )
        (progn
          (if (= (strcase pref T) "excel")
            (progn
              (c:ASXL)
            )
            (progn
              (print "Reescribir adecuadamente la preferencia del archivo")
            )
          )
        )
      )
    )
  )
)
