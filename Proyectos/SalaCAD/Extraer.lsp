(defun ExportBlockAttributesComa (blockName filePath)
  (setq ss (ssget "X" (list (cons 2 blockName))))
  (if ss
    (progn
      (if filePath
        (progn
          (setq file (open filePath "a"))
          (setq i 0)
          (while (< i (sslength ss))
            (setq ent (ssname ss i)
                  entObj (vlax-ename->vla-object ent)
                  attribs (vl-remove-if-not 'vla-HasAttributes (list entObj))
                  coord (cdr (assoc 10 (entget ent)))
                  rot (cdr (assoc 50 (entget ent))))
            (write-line (strcat "\nBlock:" blockName ",X:" (rtos (car coord)) ",Y:" (rtos (cadr coord) 2) " Rotation:" (rtos rot 2 2)) file)
            (foreach attrib attribs
              (foreach att (vlax-invoke attrib 'GetAttributes)
                (write-line (strcat "Tag:" (vla-get-TagString att) ",Value:" (vla-get-TextString att)) file)
              )
            )
            (setq i (1+ i))
          )
          (close file)
          (princ (strcat "\nAttributes exported to " filePath))
        )
        (princ "\nNo file specified."))
    )
    (princ "\nNo instances of the specified block found.")
  )
  (princ)
)

(defun ExportBlockAttributesEspacio (blockName filePath)
  (setq ss (ssget "X" (list (cons 2 blockName))))
  (if ss
    (progn
      (if filePath
        (progn
          (setq file (open filePath "a"))
          (setq i 0)
          (while (< i (sslength ss))
            (setq ent (ssname ss i)
                  entObj (vlax-ename->vla-object ent)
                  attribs (vl-remove-if-not 'vla-HasAttributes (list entObj))
                  coord (cdr (assoc 10 (entget ent)))
                  rot (cdr (assoc 50 (entget ent))))
            (write-line (strcat "\nBlock:" blockName " X:" (rtos (car coord)) " Y:" (rtos (cadr coord) 2) " Rotation:" (rtos rot 2 2)) file)
            (foreach attrib attribs
              (foreach att (vlax-invoke attrib 'GetAttributes)
                (write-line (strcat "Tag:" (vla-get-TagString att) " Value:" (vla-get-TextString att)) file)
              )
            )
            (setq i (1+ i))
          )
          (close file)
          (princ (strcat "\nAttributes exported to " filePath))
        )
        (princ "\nNo file specified."))
    )
    (princ "\nNo instances of the specified block found.")
  )
  (princ)
)

(defun c:ExportToTextComa ()
  (setq filePath (getfiled "Save attributes to" "" "txt" 1))
  (setq file (open filePath "w"))
  (write-line "Archivo")
  (close file)
  (ExportBlockAttributesComa "mouse" filePath)
  (ExportBlockAttributesComa "Mesa" filePath)
  (ExportBlockAttributesComa "Keyboard" filePath)
  (ExportBlockAttributesComa "Televisor" filePath)
  (ExportBlockAttributesComa "Silla" filePath)
  (ExportBlockAttributesComa "Monitor" filePath)
)  
(defun c:ExportToTextEspacio ()
  (setq filePath (getfiled "Save attributes to" "" "txt" 1))
  (setq file (open filePath "w"))
  (write-line "Archivo")
  (close file)
  (ExportBlockAttributesEspacio "mouse" filePath)
  (ExportBlockAttributesEspacio "Mesa" filePath)
  (ExportBlockAttributesEspacio "Keyboard" filePath)
  (ExportBlockAttributesEspacio "Televisor" filePath)
  (ExportBlockAttributesEspacio "Silla" filePath)
  (ExportBlockAttributesEspacio "Monitor" filePath)
)  

(defun vla-HasAttributes (blk)
  (if (vlax-property-available-p blk 'HasAttributes)
    (vlax-get blk 'HasAttributes)
    nil
  )
)

(defun vl-remove-if-not (fn lst)
  (apply 'append (mapcar '(lambda (x) (if (apply fn (list x)) (list x) '())) lst))
)

(defun c:ExportBlockAttributesProto (/ blockName ss i ent attribs attrib att filePath file x y rotation)
  (setq blockName (strcase (getstring "\nEnter the block name: ")) ; Get block name from the user
        ss (ssget "X" (list (cons 2 blockName)))) ; Select all instances of the block
  (if ss
    (progn
      (setq filePath (getfiled "Save attributes to" "" "txt" 1)) ; Prompt user to specify the output file
      (if filePath
        (progn
          (setq file (open filePath "w"))
          (setq i 0)
          (while (< i (sslength ss))
            (setq ent (ssname ss i)
                  entObj (vlax-ename->vla-object ent)
                  attribs (vl-remove-if-not 'vla-HasAttributes (list entObj))
                  coord (cdr (assoc 10 (entget ent)))
                  rot (cdr (assoc 50 (entget ent))))
            (write-line (strcat "Block: " blockName ", X: " (rtos (car coord)) ", Y: " (rtos (cadr coord) 2) ", Rotation: " (rtos rot 2 2)) file)
            (foreach attrib attribs
              (foreach att (vlax-invoke attrib 'GetAttributes)
                (write-line (strcat "  Tag: " (vla-get-TagString att) ", Value: " (vla-get-TextString att)) file)
              )
            )
            (setq i (1+ i))
          )
          (close file)
          (princ (strcat "\nAttributes exported to " filePath))
        )
        (princ "\nNo file specified."))
    )
    (princ "\nNo instances of the specified block found.")
  )
  (princ)
)
